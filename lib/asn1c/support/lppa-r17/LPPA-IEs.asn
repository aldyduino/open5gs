-- 3GPP TS 36.455 version 17.1.0 Release 17 (2023-04)
-- Section 9.3.5 Information Element definitions

-- ASN1START
-- **************************************************************
--
-- Information Element Definitions
--
-- **************************************************************

LPPA-IEs {
itu-t (0) identified-organization (4) etsi (0) mobileDomain (0) 
eps-Access (21) modules (3) lppa (6) version1 (1) lppa-IEs (2) }

DEFINITIONS AUTOMATIC TAGS ::= 

BEGIN

IMPORTS	
    
    id-MeasurementQuantities-Item,
    id-ResultsPerSSB-Index-List,
    id-ResultsPerSSB-Index-Item,
    id-NR-CGI,
    maxCellineNB,
    maxCellReport,
    maxNrOfErrors,
    maxNoMeas,
    maxnoOTDOAtypes,
    maxServCell,
    id-InterRATMeasurementQuantities-Item,
    id-WLANMeasurementQuantities-Item,
    maxGERANMeas,
    maxUTRANMeas,
    maxNRmeas,
    maxResultsPerSSBIndex,
    maxCellineNB-ext,
    maxWLANchannels,
    maxMBSFN-Allocations,
    maxnoFreqHoppingBandsMinusOne,
    maxNrOfPosSImessage,
    maxnoAssistInfoFailureListItems,
    maxNrOfSegments,
    maxNrOfPosSIBs

FROM LPPA-Constants

    Criticality,
    LPPATransactionID,
    ProcedureCode,
    ProtocolIE-ID,
    TriggeringMessage

FROM LPPA-CommonDataTypes

    ProtocolExtensionContainer{},
    ProtocolIE-Single-Container{},
    
    LPPA-PROTOCOL-EXTENSION,
    LPPA-PROTOCOL-IES
FROM LPPA-Containers;

-- A

Add-OTDOACells ::= SEQUENCE (SIZE (1.. maxCellineNB-ext)) OF SEQUENCE {
    add-OTDOACellInfo				Add-OTDOACell-Information,
    iE-Extensions					ProtocolExtensionContainer { {Add-OTDOACells-ExtIEs} } OPTIONAL,
    ...
}

Add-OTDOACells-ExtIEs LPPA-PROTOCOL-EXTENSION ::= {
    ...
}

Add-OTDOACell-Information ::= SEQUENCE (SIZE (1..maxnoOTDOAtypes)) OF OTDOACell-Information-Item

Assistance-Information ::= SEQUENCE {
    systemInformation				SystemInformation,
    iE-Extensions					ProtocolExtensionContainer { { Assistance-Information-ExtIEs} } OPTIONAL,
    ...
}

Assistance-Information-ExtIEs LPPA-PROTOCOL-EXTENSION ::= {
    ...
}

AssistanceInformationFailureList ::= SEQUENCE (SIZE (1..maxnoAssistInfoFailureListItems)) OF SEQUENCE {
    posSIB-Type						PosSIB-Type,
    outcome							Outcome,
    iE-Extensions					ProtocolExtensionContainer { {AssistanceInformationFailureList-ExtIEs} }	OPTIONAL,
    ...
}

AssistanceInformationFailureList-ExtIEs LPPA-PROTOCOL-EXTENSION ::= {
    ...
}

AssistanceInformationMetaData ::= SEQUENCE {
    encrypted			ENUMERATED {true, ...}	OPTIONAL,
    gNSSID				ENUMERATED {gps, sbas, gzss, galileo, glonass, bds, ..., navic}	OPTIONAL,
    sBASID				ENUMERATED {waas, egnos, msas, gagan, ...}				OPTIONAL,
    iE-Extensions						ProtocolExtensionContainer { { AssistanceInformationMetaData-ExtIEs} }	OPTIONAL,
    ...
}

AssistanceInformationMetaData-ExtIEs LPPA-PROTOCOL-EXTENSION ::= {
    ...
}

-- B

BCCH ::= INTEGER (0..1023, ...)

BitmapsforNPRS	::= CHOICE {
    ten			BIT STRING(SIZE (10)),
    forty		BIT STRING(SIZE (40)),
    ...,
    ten-tdd		BIT STRING(SIZE (8)),
    forty-tdd	BIT STRING(SIZE (32))}

Broadcast ::= ENUMERATED {
    start,
    stop,
    ...
}

BroadcastPeriodicity ::= ENUMERATED {
    ms80,
    ms160,
    ms320,
    ms640,
    ms1280,
    ms2560,
    ms5120,
    ...
}

BSSID ::= OCTET STRING (SIZE(6))


-- C

Cause ::= CHOICE {
    radioNetwork		CauseRadioNetwork,
    protocol			CauseProtocol,
    misc				CauseMisc,
    ...
}

CauseMisc ::= ENUMERATED {
    unspecified,
    ...
}

CauseProtocol ::= ENUMERATED {
    transfer-syntax-error,
    abstract-syntax-error-reject,
    abstract-syntax-error-ignore-and-notify,
    message-not-compatible-with-receiver-state,
    semantic-error,
    unspecified,
    abstract-syntax-error-falsely-constructed-message,
    ...
}

CauseRadioNetwork ::= ENUMERATED {
    unspecified,
    requested-item-not-supported,
    requested-item-temporarily-not-available,
    ...

}

Cell-Portion-ID ::= INTEGER (0..255,... , 256..4095)

CPLength ::= ENUMERATED {
    normal,
    extended,
    ...
}

CriticalityDiagnostics ::= SEQUENCE {
    procedureCode					ProcedureCode					OPTIONAL,
    triggeringMessage				TriggeringMessage				OPTIONAL,
    procedureCriticality			Criticality						OPTIONAL,
    lppatransactionID				LPPATransactionID				OPTIONAL,
    iEsCriticalityDiagnostics		CriticalityDiagnostics-IE-List	OPTIONAL,
    iE-Extensions					ProtocolExtensionContainer { {CriticalityDiagnostics-ExtIEs} }	OPTIONAL,
    ...
}


CriticalityDiagnostics-ExtIEs LPPA-PROTOCOL-EXTENSION ::= {
    ...
}

CriticalityDiagnostics-IE-List ::= SEQUENCE (SIZE (1..maxNrOfErrors)) OF
    SEQUENCE {
        iECriticality			Criticality,
        iE-ID					ProtocolIE-ID,
        typeOfError				TypeOfError,
        iE-Extensions			ProtocolExtensionContainer { {CriticalityDiagnostics-IE-List-ExtIEs} } OPTIONAL,
        ...
}

CriticalityDiagnostics-IE-List-ExtIEs LPPA-PROTOCOL-EXTENSION ::= {
    ...
}

-- D

DL-Bandwidth ::= ENUMERATED {
    bw6,
    bw15,
    bw25,
    bw50,
    bw75,
    bw100,
    ...
}

-- E

E-CID-MeasurementResult ::= SEQUENCE {
    servingCell-ID					ECGI,
    servingCellTAC					TAC,
    e-UTRANAccessPointPosition		E-UTRANAccessPointPosition	OPTIONAL,
    measuredResults					MeasuredResults				OPTIONAL,
    ...
}

ECGI ::= SEQUENCE {
    pLMN-Identity				PLMN-Identity,
    eUTRANcellIdentifier		EUTRANCellIdentifier,
    iE-Extensions				ProtocolExtensionContainer { {ECGI-ExtIEs} } OPTIONAL,
    ...
}

ECGI-ExtIEs LPPA-PROTOCOL-EXTENSION ::= {
    ...
}

EUTRANCellIdentifier ::= BIT STRING (SIZE (28))

EARFCN ::= INTEGER (0..65535, ..., 65536..262143)

E-UTRANAccessPointPosition ::= SEQUENCE {
    latitudeSign				ENUMERATED {north, south},
    latitude					INTEGER (0..8388607),
    longitude					INTEGER (-8388608..8388607),
    directionOfAltitude			ENUMERATED {height, depth},
    altitude					INTEGER (0..32767),
    uncertaintySemi-major		INTEGER (0..127),
    uncertaintySemi-minor		INTEGER (0..127),
    orientationOfMajorAxis		INTEGER (0..179),
    uncertaintyAltitude			INTEGER (0..127),
    confidence					INTEGER (0..100),
    ...
}

-- F
-- G
-- H

HESSID ::= OCTET STRING (SIZE(6))


-- I

InterRATMeasurementQuantities ::= SEQUENCE (SIZE (0.. maxNoMeas)) OF ProtocolIE-Single-Container { {InterRATMeasurementQuantities-ItemIEs} }

InterRATMeasurementQuantities-ItemIEs LPPA-PROTOCOL-IES ::= {
    { ID id-InterRATMeasurementQuantities-Item	CRITICALITY reject	TYPE InterRATMeasurementQuantities-Item PRESENCE mandatory}}

InterRATMeasurementQuantities-Item ::= SEQUENCE {
    interRATMeasurementQuantitiesValue			InterRATMeasurementQuantitiesValue,
    iE-Extensions								ProtocolExtensionContainer { { InterRATMeasurementQuantitiesValue-ExtIEs} } OPTIONAL,
    ...
}

InterRATMeasurementQuantitiesValue-ExtIEs LPPA-PROTOCOL-EXTENSION ::= {
    ...
}

InterRATMeasurementQuantitiesValue ::= ENUMERATED {
    geran,
    utran,
    ...,
    nr
}

InterRATMeasurementResult ::= SEQUENCE (SIZE (1.. maxNoMeas)) OF InterRATMeasuredResultsValue

InterRATMeasuredResultsValue ::= CHOICE {
    resultGERAN			ResultGERAN,
    resultUTRAN			ResultUTRAN,
    ...,
    resultNR			ResultNR
}

-- J
-- K
-- L
-- M

Measurement-ID ::= INTEGER (1..15, ...)

MeasurementPeriodicity ::= ENUMERATED {
    ms120,
    ms240,
    ms480,
    ms640,
    ms1024,
    ms2048,
    ms5120,
    ms10240,
    min1,
    min6,
    min12,
    min30,
    min60,
    ...
}

MeasurementQuantities ::= SEQUENCE (SIZE (1.. maxNoMeas)) OF ProtocolIE-Single-Container { {MeasurementQuantities-ItemIEs} }

MeasurementQuantities-ItemIEs LPPA-PROTOCOL-IES ::= {
    { ID id-MeasurementQuantities-Item	CRITICALITY reject	TYPE MeasurementQuantities-Item		PRESENCE mandatory}
}

MeasurementQuantities-Item ::= SEQUENCE {
    measurementQuantitiesValue							MeasurementQuantitiesValue,
    iE-Extensions										ProtocolExtensionContainer { { MeasurementQuantitiesValue-ExtIEs} } OPTIONAL,
    ...
}

MeasurementQuantitiesValue-ExtIEs LPPA-PROTOCOL-EXTENSION ::= {
    ...
}

MeasurementQuantitiesValue ::= ENUMERATED {
    cell-ID,
    angleOfArrival,
    timingAdvanceType1,
    timingAdvanceType2,
    rSRP,
    rSRQ,
    ...
}

MeasuredResults ::= SEQUENCE (SIZE (1.. maxNoMeas)) OF MeasuredResultsValue


MeasuredResultsValue ::= CHOICE { 
    valueAngleOfArrival				INTEGER (0..719),
    valueTimingAdvanceType1			INTEGER (0..7690),
    valueTimingAdvanceType2			INTEGER (0..7690),
    resultRSRP						ResultRSRP,
    resultRSRQ						ResultRSRQ,
    ...
}

MBSFNsubframeConfiguration ::= SEQUENCE (SIZE (1.. maxMBSFN-Allocations)) OF MBSFNsubframeConfigurationValue

MBSFNsubframeConfigurationValue ::=			SEQUENCE {
    radioframeAllocationPeriod			ENUMERATED {n1, n2, n4, n8, n16, n32},
    radioframeAllocationOffset			INTEGER (0..7),
    subframeAllocation					Subframeallocation
}


-- N

NarrowBandIndex ::= INTEGER (0..15,...)

NRCellIdentity ::= BIT STRING (SIZE(36))

NR-CGI ::= SEQUENCE {
    pLMN-Identity		PLMN-Identity,
    nRCellIdentity		NRCellIdentity,
    iE-Extensions		ProtocolExtensionContainer { {NR-CGI-ExtIEs} } OPTIONAL,
    ...
}

NR-CGI-ExtIEs LPPA-PROTOCOL-EXTENSION ::= {
    ...
}

NPRSConfiguration ::=			SEQUENCE {
    nPRSSubframePartA			NPRSSubframePartA 		OPTIONAL,
    nPRSSubframePartB			NPRSSubframePartB 		OPTIONAL,
    ...
}

NPRSMutingConfiguration ::= CHOICE {
    two 				BIT STRING (SIZE (2)),
    four 				BIT STRING (SIZE (4)),
    eight 				BIT STRING (SIZE (8)),
    sixteen 			BIT STRING (SIZE (16)),
    ...
}

NPRSSubframePartA ::=			SEQUENCE {
    bitmapsforNPRS				BitmapsforNPRS,
    nPRSMutingConfiguration		NPRSMutingConfiguration 		OPTIONAL,
    ...
}

NPRSSubframePartB ::=			SEQUENCE {
    numberofNPRSOneOccasion		ENUMERATED {sf10, sf20, sf40, sf80, sf160, sf320, sf640, sf1280, ..., sf2560},
    periodicityofNPRS			ENUMERATED {sf160, sf320, sf640, sf1280, ..., sf2560},
    startingsubframeoffset		ENUMERATED {zero, one-Eighth, two-Eighths, three-Eighths, four-Eighths, five-Eighths, six-Eighths, seven-Eighths, ...},
    nPRSMutingConfiguration		NPRSMutingConfiguration 		OPTIONAL,
    ...,
    sIB1-NB-Subframe-TDD			ENUMERATED {	sf0, sf4, sf0and5, ...} 		OPTIONAL	

}

NumberOfAntennaPorts ::= ENUMERATED {
        n1-or-n2,
        n4,
        ...
}

NumberOfDlFrames ::= ENUMERATED {
        sf1,
        sf2,
        sf4,
        sf6,
        ...
}


NumberOfDlFrames-Extended ::= INTEGER (1..160,...)

NumberOfFrequencyHoppingBands ::= ENUMERATED {
    twobands,
    fourbands,
    ...
}

NPRSSequenceInfo ::= INTEGER (0..174,...)


NRARFCN ::= INTEGER (0.. 3279165)

NRPCI ::= INTEGER (0..1007)

-- O

OffsetNBChanneltoEARFCN ::= ENUMERATED {
        minusTen,
        minusNine,
        minusEight,
        minusSeven,
        minusSix,
        minusFive,
        minusFour,
        minusThree,
        minusTwo,
        minusOne,
        minusZeroDotFive,
        zero,
        one,
        two,
        three,
        four,
        five,
        six,
        seven,
        eight,
        nine,
        ...
}

OperationModeInfo ::= ENUMERATED {
        inband,
        guardband,
        standalone,
        ...
}

OTDOACells ::= SEQUENCE (SIZE (1.. maxCellineNB)) OF SEQUENCE {
    oTDOACellInfo					OTDOACell-Information,
    iE-Extensions					ProtocolExtensionContainer { {OTDOACells-ExtIEs} } OPTIONAL,
    ...
}

OTDOACells-ExtIEs LPPA-PROTOCOL-EXTENSION ::= {
    ...
}

OTDOACell-Information ::= SEQUENCE (SIZE (1..maxnoOTDOAtypes)) OF OTDOACell-Information-Item

OTDOACell-Information-Item ::= CHOICE {
    pCI							PCI,
    cellId						ECGI,
    tAC							TAC,
    eARFCN						EARFCN,
    pRS-Bandwidth				PRS-Bandwidth,
    pRS-ConfigurationIndex		PRS-Configuration-Index, 
    cPLength					CPLength,
    numberOfDlFrames			NumberOfDlFrames,
    numberOfAntennaPorts		NumberOfAntennaPorts,
    sFNInitialisationTime		SFNInitialisationTime,
    e-UTRANAccessPointPosition	E-UTRANAccessPointPosition,
    ...,
    pRSMutingConfiguration		PRSMutingConfiguration,
    prsid						PRS-ID,
    tpid						TP-ID,
    tpType						TP-Type,
    numberOfDlFrames-Extended	NumberOfDlFrames-Extended,
    crsCPlength					CPLength,
    mBSFNsubframeConfiguration	MBSFNsubframeConfiguration,
    nPRSConfiguration			NPRSConfiguration,
    offsetNBChanneltoEARFCN		OffsetNBChanneltoEARFCN,
    operationModeInfo			OperationModeInfo,
    nPRS-ID						INTEGER (0..4095, ...), 
    dL-Bandwidth				DL-Bandwidth,
    pRSOccasionGroup			PRSOccasionGroup,
    pRSFreqHoppingConfig		PRSFrequencyHoppingConfiguration,
    repetitionNumberofSIB1-NB	RepetitionNumberofSIB1-NB,
    nPRSSequenceInfo			NPRSSequenceInfo,
    nPRSType2					NPRSConfiguration,
    tddConfiguration			TDDConfiguration
}

OTDOA-Information-Item ::= ENUMERATED {
        pci,
        cellid,
        tac,
        earfcn,
        prsBandwidth,
        prsConfigIndex,
        cpLength,
        noDlFrames,
        noAntennaPorts,
        sFNInitTime,
        ...,
        e-UTRANAccessPointPosition,
        prsmutingconfiguration,
        prsid,
        tpid,
        tpType,
        crsCPlength,
        mBSFNsubframeConfiguration,
        nPRSConfiguration,
        offsetNBChannelNumbertoEARFCN,
        operationModeInfo,
        nPRS-ID,
        dlBandwidth,
        multipleprsConfigurationsperCell,
        prsOccasionGroup,
        prsFrequencyHoppingConfiguration,
        repetitionNumberofSIB1-NB,
        nPRSSequenceInfo,
        nPRSType2,
        tddConfig
}

Outcome ::= ENUMERATED {
        failed,
        ...
}

-- P

PCI ::= INTEGER (0..503, ...)

PhysCellIDGERAN ::= INTEGER (0..63, ...)

PhysCellIDUTRA-FDD ::= INTEGER (0..511, ...)

PhysCellIDUTRA-TDD ::= INTEGER (0..127, ...)

PLMN-Identity ::= OCTET STRING (SIZE(3))

PosSIBs ::= SEQUENCE (SIZE (1.. maxNrOfPosSIBs)) OF SEQUENCE {
    posSIB-Type						PosSIB-Type,
    posSIB-Segments					PosSIB-Segments,
    assistanceInformationMetaData	AssistanceInformationMetaData		OPTIONAL,
    broadcastPriority				INTEGER (1..16,...)				OPTIONAL,
    iE-Extensions					ProtocolExtensionContainer { { PosSIBs-ExtIEs} }	OPTIONAL,
    ...
}

PosSIBs-ExtIEs LPPA-PROTOCOL-EXTENSION ::= {
    ...
}

PosSIB-Segments ::= SEQUENCE (SIZE (1.. maxNrOfSegments)) OF SEQUENCE {
    assistanceDataSIBelement			OCTET STRING,
    iE-Extensions						ProtocolExtensionContainer { { PosSIB-Segments-ExtIEs} }	OPTIONAL,
    ...
}

PosSIB-Segments-ExtIEs LPPA-PROTOCOL-EXTENSION ::= {
    ...
}


PosSIB-Type ::= ENUMERATED {
    posSibType1-1, 
    posSibType1-2, 
    posSibType1-3, 
    posSibType1-4, 
    posSibType1-5,
    posSibType1-6, 
    posSibType1-7, 
    posSibType2-1, 
    posSibType2-2, 
    posSibType2-3,
    posSibType2-4, 
    posSibType2-5, 
    posSibType2-6, 
    posSibType2-7, 
    posSibType2-8,
    posSibType2-9, 
    posSibType2-10, 
    posSibType2-11, 
    posSibType2-12, 
    posSibType2-13, 
    posSibType2-14, 
    posSibType2-15, 
    posSibType2-16,
    posSibType2-17, 
    posSibType2-18, 
    posSibType2-19,
    posSibType3-1,
    ...,
    posSibType4-1,
    posSibType5-1,
    posSibType2-24,
    posSibType2-25
}

PRS-Bandwidth ::= ENUMERATED {
        bw6,
        bw15,
        bw25,
        bw50,
        bw75,
        bw100,
        ...
}

PRS-Configuration-Index ::= INTEGER (0..4095, ...)

PRS-ID	::= INTEGER (0..4095, ...)

PRSMutingConfiguration ::= CHOICE {
    two 			BIT STRING (SIZE (2)),
    four 			BIT STRING (SIZE (4)),
    eight 			BIT STRING (SIZE (8)),
    sixteen 		BIT STRING (SIZE (16)),
    ...,
    thirty-two						BIT STRING (SIZE (32)),
    sixty-four						BIT STRING (SIZE (64)),
    one-hundred-and-twenty-eight	BIT STRING (SIZE (128)),
    two-hundred-and-fifty-six		BIT STRING (SIZE (256)),
    five-hundred-and-twelve			BIT STRING (SIZE (512)),
    one-thousand-and-twenty-four	BIT STRING (SIZE (1024))
}

PRSOccasionGroup ::= ENUMERATED {
    og2,
    og4,
    og8,
    og16,
    og32,
    og64,
    og128,
    ...
}

PRSFrequencyHoppingConfiguration ::= SEQUENCE {
    noOfFreqHoppingBands		NumberOfFrequencyHoppingBands,
    bandPositions				SEQUENCE(SIZE (1..maxnoFreqHoppingBandsMinusOne)) OF NarrowBandIndex,
    iE-Extensions				ProtocolExtensionContainer { { PRSFrequencyHoppingConfiguration-Item-IEs} } OPTIONAL,
    ...
}

PRSFrequencyHoppingConfiguration-Item-IEs LPPA-PROTOCOL-EXTENSION ::= {
    ...
}

-- Q
-- R

RepetitionNumberofSIB1-NB ::= ENUMERATED {
    r4,
    r8,
    r16,
    ...
}

ReportCharacteristics ::= ENUMERATED {
    onDemand,
    periodic,
    ...
}

RequestedSRSTransmissionCharacteristics ::= SEQUENCE {
    numberOfTransmissions	INTEGER (0..500, ...),
    bandwidth				INTEGER (1..100, ...),
    ...
}

ResultRSRP ::= SEQUENCE (SIZE (1.. maxCellReport)) OF ResultRSRP-Item

ResultRSRP-Item ::= SEQUENCE {
    pCI				PCI,
    eARFCN			EARFCN,
    eCGI			ECGI OPTIONAL,
    valueRSRP		ValueRSRP,
    iE-Extensions	ProtocolExtensionContainer { { ResultRSRP-Item-ExtIEs} } OPTIONAL,
    ...
}

ResultRSRP-Item-ExtIEs LPPA-PROTOCOL-EXTENSION ::= {
    ...
}

ResultRSRQ ::= SEQUENCE (SIZE (1.. maxCellReport)) OF ResultRSRQ-Item

ResultRSRQ-Item ::= SEQUENCE {
    pCI				PCI,
    eARFCN			EARFCN,
    eCGI			ECGI OPTIONAL,
    valueRSRQ		ValueRSRQ,
    iE-Extensions	ProtocolExtensionContainer { { ResultRSRQ-Item-ExtIEs} } OPTIONAL,
    ...
}

ResultRSRQ-Item-ExtIEs LPPA-PROTOCOL-EXTENSION ::= {
    ...
}

ResultGERAN ::= SEQUENCE (SIZE (1.. maxGERANMeas)) OF ResultGERAN-Item

ResultGERAN-Item ::= SEQUENCE {
    bCCH				BCCH,
    physCellIDGERAN		PhysCellIDGERAN,
    rSSI				RSSI,
    iE-Extensions		ProtocolExtensionContainer { { ResultGERAN-Item-ExtIEs} } OPTIONAL,
    ...
}

ResultGERAN-Item-ExtIEs LPPA-PROTOCOL-EXTENSION ::= {
    ...
}

ResultUTRAN ::= SEQUENCE (SIZE (1.. maxUTRANMeas)) OF ResultUTRAN-Item

ResultUTRAN-Item ::= SEQUENCE {
    uARFCN				UARFCN,
    physCellIDUTRAN		CHOICE {
        physCellIDUTRA-FDD		PhysCellIDUTRA-FDD,
        physCellIDUTRA-TDD		PhysCellIDUTRA-TDD
    },
    uTRA-RSCP			UTRA-RSCP OPTIONAL,
    uTRA-EcN0			UTRA-EcN0 OPTIONAL,
    iE-Extensions		ProtocolExtensionContainer { { ResultUTRAN-Item-ExtIEs} } OPTIONAL,
    ...
}

ResultUTRAN-Item-ExtIEs LPPA-PROTOCOL-EXTENSION ::= {
    ...
}

ResultNR ::= SEQUENCE (SIZE (1.. maxNRmeas)) OF ResultNR-Item

ResultNR-Item ::= SEQUENCE {
    nRARFCN				NRARFCN,
    nRPCI				NRPCI,
    sS-NRRSRP			SS-NRRSRP	OPTIONAL,
    sS-NRRSRQ			SS-NRRSRQ	OPTIONAL,
    iE-Extensions		ProtocolExtensionContainer { { ResultNR-Item-ExtIEs} } OPTIONAL,
    ...
}

ResultNR-Item-ExtIEs LPPA-PROTOCOL-EXTENSION ::= {
    { ID id-ResultsPerSSB-Index-List							CRITICALITY ignore	EXTENSION ResultsPerSSB-Index-List					PRESENCE optional}|
    { ID id-NR-CGI												CRITICALITY ignore	EXTENSION NR-CGI											PRESENCE optional},
    ...
}


ResultsPerSSB-Index-List ::= SEQUENCE (SIZE(1..maxResultsPerSSBIndex)) OF ResultsPerSSB-Index-Item

ResultsPerSSB-Index-Item ::=SEQUENCE {
    sSB-Index					SSB-Index,
    sS-NRRSRPBeamValue			SS-NRRSRP			OPTIONAL,
    sS-NRRSRQBeamValue			SS-NRRSRQ 				OPTIONAL,
    iE-Extensions				ProtocolExtensionContainer { { ResultsPerSSB-Index-Item-ExtIEs} }	OPTIONAL,
    ...
}

ResultsPerSSB-Index-Item-ExtIEs LPPA-PROTOCOL-EXTENSION ::= {
    ...
}

RSSI ::= INTEGER (0..63, ...)


-- S

SFNInitialisationTime ::= BIT STRING (SIZE (64))

SRSConfigurationForAllCells ::= SEQUENCE (SIZE (1.. maxServCell)) OF SRSConfigurationForOneCell

SRSConfigurationForOneCell ::= SEQUENCE {
    pci							PCI,
    ul-earfcn					EARFCN,
    ul-bandwidth				ENUMERATED {n6, n15, n25, n50, n75, n100},
    ul-cyclicPrefixLength		CPLength,
    srs-BandwidthConfig			ENUMERATED {bw0, bw1, bw2, bw3, bw4, bw5, bw6, bw7},
    srs-Bandwidth				ENUMERATED {bw0, bw1, bw2, bw3},
    srs-AntennaPort				ENUMERATED {an1, an2, an4, ...},
    srs-HoppingBandwidth		ENUMERATED {hbw0, hbw1, hbw2, hbw3},
    srs-cyclicShift				ENUMERATED {cs0, cs1, cs2, cs3, cs4, cs5, cs6, cs7},
    srs-ConfigIndex				INTEGER (0..1023),
    maxUpPts					ENUMERATED {true}			OPTIONAL,	-- Cond ifTDD
    transmissionComb			INTEGER (0..1),
    freqDomainPosition			INTEGER (0..23),
    groupHoppingEnabled			BOOLEAN,
    deltaSS						INTEGER (0..29)				OPTIONAL,
    sfnInitialisationTime		SFNInitialisationTime,
    ...
}


Subframeallocation ::= CHOICE {
    oneFrame						BIT STRING (SIZE(6)),
    fourFrames						BIT STRING (SIZE(24))
}

SS-NRRSRP ::= INTEGER (0..127)

SS-NRRSRQ ::= INTEGER (0..127)

SSB-Index ::= INTEGER (0..63)

SSID ::= OCTET STRING (SIZE(1..32))

SystemInformation ::= SEQUENCE (SIZE (1.. maxNrOfPosSImessage)) OF SEQUENCE {
    broadcastPeriodicity				BroadcastPeriodicity,
    posSIBs								PosSIBs,
    iE-Extensions						ProtocolExtensionContainer { { SystemInformation-ExtIEs} }	OPTIONAL,
    ...
}

SystemInformation-ExtIEs LPPA-PROTOCOL-EXTENSION ::= {
    ...
}

-- T

TAC ::= OCTET STRING (SIZE(2))

TDDConfiguration ::= SEQUENCE {
    subframeAssignment				ENUMERATED { sa0, sa1, sa2, sa3, sa4, sa5, sa6, ... },
    iE-Extensions					ProtocolExtensionContainer { { TDDConfiguration-ExtIEs} }	OPTIONAL,
    ...
}

TDDConfiguration-ExtIEs LPPA-PROTOCOL-EXTENSION ::= {
    ...
}


TP-ID ::= INTEGER (0..4095, ...)

TP-Type ::= ENUMERATED { prs-only-tp, ... }

TypeOfError ::= ENUMERATED {
    not-understood,
    missing,
    ...
}



-- U

ULConfiguration ::= SEQUENCE {
    pci							PCI,
    ul-earfcn					EARFCN,
    timingAdvanceType1			INTEGER (0..7690) 			OPTIONAL,
    timingAdvanceType2			INTEGER (0..7690)			OPTIONAL,
    numberOfTransmissions		INTEGER (0..500,...),
    srsConfiguration			SRSConfigurationForAllCells,
    ...
}

UARFCN ::= INTEGER (0..16383, ...)

UTRA-EcN0 ::= INTEGER (0..49, ...)

UTRA-RSCP ::= INTEGER (-5..91, ...)

-- V

ValueRSRP ::= INTEGER (0..97, ...)

ValueRSRQ ::= INTEGER (0..34, ...)

-- W

WLANMeasurementQuantities ::= SEQUENCE (SIZE (0.. maxNoMeas)) OF ProtocolIE-Single-Container { {WLANMeasurementQuantities-ItemIEs} }

WLANMeasurementQuantities-ItemIEs LPPA-PROTOCOL-IES ::= {
    { ID id-WLANMeasurementQuantities-Item	CRITICALITY reject	TYPE WLANMeasurementQuantities-Item PRESENCE mandatory}}

WLANMeasurementQuantities-Item ::= SEQUENCE {
    wLANMeasurementQuantitiesValue			WLANMeasurementQuantitiesValue,
    iE-Extensions							ProtocolExtensionContainer { { WLANMeasurementQuantitiesValue-ExtIEs} } OPTIONAL,
    ...
}

WLANMeasurementQuantitiesValue-ExtIEs LPPA-PROTOCOL-EXTENSION ::= {
    ...
}

WLANMeasurementQuantitiesValue ::= ENUMERATED {
    wlan,
    ...
}


WLANMeasurementResult ::= SEQUENCE (SIZE (1..maxNoMeas)) OF WLANMeasurementResult-Item

WLANMeasurementResult-Item ::= SEQUENCE {
    wLAN-RSSI			WLAN-RSSI,
    sSID				SSID					OPTIONAL,
    bSSID				BSSID					OPTIONAL,
    hESSID				HESSID					OPTIONAL,
    operatingClass		WLANOperatingClass		OPTIONAL,
    countryCode			WLANCountryCode			OPTIONAL,
    wLANChannelList		WLANChannelList			OPTIONAL,
    wLANBand			WLANBand				OPTIONAL,
    iE-Extensions		ProtocolExtensionContainer { { WLANMeasurementResult-Item-ExtIEs } }	OPTIONAL,
    ...
}

WLANMeasurementResult-Item-ExtIEs	LPPA-PROTOCOL-EXTENSION ::= {
    ...
}

WLAN-RSSI ::= INTEGER (0..141, ...)

WLANBand ::= ENUMERATED {band2dot4, band5, ...}

WLANChannelList ::= SEQUENCE (SIZE (1..maxWLANchannels)) OF WLANChannel

WLANChannel ::= INTEGER (0..255)

WLANCountryCode ::= ENUMERATED {
    unitedStates,
    europe,
    japan,
    global,
    ...
}

WLANOperatingClass ::= INTEGER (0..255)

-- X
-- Y
-- Z

END
-- ASN1STOP
