-- 3GPP TS 29.171 version 17.3.0 Release 17 (2023-07)
-- Section 7.5.8 Container Definitions

-- **************************************************************
--
-- Container definitions
--
-- **************************************************************

LCS-AP-Containers {
itu-t (0) identified-organization (4) etsi (0) mobileDomain (0)
eps-Access (21) modules (3) lcs-AP (4) version1 (1) lcs-AP-Containers (5)}

DEFINITIONS AUTOMATIC TAGS ::=

BEGIN

-- **************************************************************
--
-- IE parameter types from other modules.
--
-- **************************************************************

IMPORTS
	Criticality,
	Presence,
	ProtocolExtensionID,
	ProtocolIE-ID
FROM LCS-AP-CommonDataTypes

	maxProtocolExtensions,
	maxProtocolIEs
FROM LCS-AP-Constants;

-- **************************************************************
--
-- Class Definition for Protocol IEs
--
-- **************************************************************

LCS-AP-PROTOCOL-IES ::= CLASS {
	&id				ProtocolIE-ID	UNIQUE,
	&criticality	Criticality		DEFAULT ignore,
	&Value,
	&presence		Presence
}
WITH SYNTAX {
	ID					&id
	CRITICALITY			&criticality
	TYPE				&Value
	PRESENCE			&presence
}

-- **************************************************************
--
-- Class Definition for Protocol Extensions
--
-- **************************************************************

LCS-AP-PROTOCOL-EXTENSION ::= CLASS {
	&id				ProtocolExtensionID		UNIQUE,
	&criticality	Criticality				DEFAULT ignore,
	&Extension,
	&presence		Presence
}
WITH SYNTAX {
	ID					&id
	CRITICALITY			&criticality
	EXTENSION			&Extension
	PRESENCE			&presence
}

-- **************************************************************
--
-- Container for Protocol IEs
--
-- **************************************************************

ProtocolIE-Container {LCS-AP-PROTOCOL-IES : IEsSetParam} ::=
	SEQUENCE (SIZE (0..maxProtocolIEs)) OF
	ProtocolIE-Field {{IEsSetParam}}

ProtocolIE-Field {LCS-AP-PROTOCOL-IES : IEsSetParam} ::= SEQUENCE {
	id				LCS-AP-PROTOCOL-IES.&id				({IEsSetParam}),
	criticality		LCS-AP-PROTOCOL-IES.&criticality	({IEsSetParam}{@id}),
	value			LCS-AP-PROTOCOL-IES.&Value			({IEsSetParam}{@id})
}

-- **************************************************************
--
-- Container Lists for Protocol IE Containers
--
-- **************************************************************

ProtocolIE-ContainerList {INTEGER : lowerBound, INTEGER : upperBound, LCS-AP-PROTOCOL-IES : IEsSetParam} ::=
	SEQUENCE (SIZE (lowerBound..upperBound)) OF
	ProtocolIE-Container {{IEsSetParam}}

-- **************************************************************
--
-- Container for Protocol Extensions
--
-- **************************************************************

ProtocolExtensionContainer {LCS-AP-PROTOCOL-EXTENSION : ExtensionSetParam} ::=
	SEQUENCE (SIZE (1..maxProtocolExtensions)) OF
	ProtocolExtensionField {{ExtensionSetParam}}

ProtocolExtensionField {LCS-AP-PROTOCOL-EXTENSION : ExtensionSetParam} ::= SEQUENCE {
	id				LCS-AP-PROTOCOL-EXTENSION.&id			({ExtensionSetParam}),
	criticality		LCS-AP-PROTOCOL-EXTENSION.&criticality	({ExtensionSetParam}{@id}),
	extensionValue	LCS-AP-PROTOCOL-EXTENSION.&Extension	({ExtensionSetParam}{@id})
}


END
